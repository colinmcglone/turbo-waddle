'This script requires the excel BOM which is generated by the BOM Web script
'Run this script to print all drawings associated with the open assembly. It will print drawings as they appear on the BOM, so if two assemblies use the same parts, you will get multiple copies of the part drawings. This script is useful for creating production binders as the drawings should come off the printer in ~the order you need them. It also prints a duplicate of all assemblies and weldments, which you will need for binders

Dim oDoc As AssemblyDocument
oDoc = ThisApplication.ActiveDocument
'Get file location
oPath = ThisDoc.Path
Dim FNamePos As Long
FNamePos = InStrRev(oDoc.FullFileName, "\", -1)                        
Dim docFName As String 
docFName = Right(oDoc.FullFileName, Len(oDoc.FullFileName) - FNamePos)
Dim sPathandName As String
sPathandName  = oDoc.FullFileName.SubString(0, oDoc.FullFileName.Length-4)
If InStr(oDoc.DisplayName, ".") > 0 Then
	oFileName = Left(oDoc.DisplayName, InStr(oDoc.DisplayName, ".") - 1)
Else
	oFileName = oDoc.DisplayName
End If
' Load Excel and check for bom
If My.Computer.FileSystem.FileExists(oPath & "\" & oFileName & "BOM.xlsx") Then
	excelApp = CreateObject("Excel.Application")
	excelApp.Visible = False
	excelApp.DisplayAlerts = False
	excelWorkbook = excelApp.Workbooks.Open(oPath & "\" & oFileName & "BOM.xlsx")
Else
	MsgBox("Excel BOM file not found, please generate with BOM Web script before running this script.")
	Exit Sub
End If

'for msgbox later
numFiles = 0
'for reprinting all weldments and assemblies (it prints all b size drawings, so dont put parts on b
Dim BList As String()
ReDim BList(1)
BList(0) = ""

'Print top level drawing
numFiles = numFiles + 1
idwPathName = oPath & "\" & oFileName & ".idw"
Dim oDrawDoc As DrawingDocument
oDrawDoc = ThisApplication.Documents.Open(idwPathName, True)
oDrawDoc.Activate
oSize = oDrawDoc.ActiveSheet.Size
oDrawDoc = ThisApplication.ActiveDocument

Dim oDrgPrintMgr As DrawingPrintManager
oDrgPrintMgr = oDrawDoc.PrintManager
With oDrgPrintMgr
	.Printer = "\\lesg-dc-003\HP Color LaserJet 5550 PCL6 Black and White"
	.ColorMode = kPrintGrayScale
	.AllColorsAsBlack = True
	.ScaleMode = kPrintFullScale
	.PrintRange = kPrintAllSheets
	.Orientation = kLandscapeOrientation
	.RemoveLineWeights = False
End With
If oSize = "9987" Then
	oDrgPrintMgr.PaperSize = PaperSizeEnum.kPaperSizeLetter
	oDrgPrintMgr.SubmitPrint
End If
If oSize = "9988" Then
	oDrgPrintMgr.PaperSize = PaperSizeEnum.kPaperSize11x17
	oDrgPrintMgr.SubmitPrint
	BList(0) = idwPathName
End If
oDrawDoc.Close (True)

'as with other scripts, we assume there will be fewer than 1000 parts in the project
For i = 2 To 1000
	'grab part number from sheet
	a = excelApp.Cells(i, 2).Value2
	idwPathName = oPath & "\" & a & ".idw"
	fileExists = False
	'make sure file exists
	If Dir(idwPathName) <> "" Then
		fileExists = True 
	End If
	If fileExists = True Then
		numFiles = numFiles + 1
		'open the drawing
		Dim oDrawDoc2 As DrawingDocument
		oDrawDoc2 = ThisApplication.Documents.Open(idwPathName, True)
		oDrawDoc2.Activate
		oSize = oDrawDoc2.ActiveSheet.Size
		oDrawDoc2 = ThisApplication.ActiveDocument

		'set up print manager
		Dim oDrgPrintMgr2 As DrawingPrintManager
		oDrgPrintMgr2 = oDrawDoc2.PrintManager
		With oDrgPrintMgr2
			.Printer = "\\lesg-dc-003\HP Color LaserJet 5550 PCL6 Black and White"
			.ColorMode = kPrintGrayScale
			.AllColorsAsBlack = True
			.ScaleMode = kPrintFullScale
			.PrintRange = kPrintAllSheets
			.Orientation = kLandscapeOrientation
			.RemoveLineWeights = False
		End With
		'check drawing size and print on the correct paper
		If oSize = "9987" Then
			oDrgPrintMgr2.PaperSize = PaperSizeEnum.kPaperSizeLetter
			oDrgPrintMgr2.SubmitPrint
		End If
		If oSize = "9988" Then
			oDrgPrintMgr2.PaperSize = PaperSizeEnum.kPaperSize11x17
			oDrgPrintMgr2.SubmitPrint
			ReDim Preserve BList(0 To UBound(BList)+1)
			BList(UBound(BList)) = idwPathName
		End If
		oDrawDoc2.Close (True)
    End If
Next i
'Print a second copy of all assembly drawings
If UBound(BList) > LBound(BList) Then
	For x = 0 To UBound(BList)-1
		Dim oDrawDoc3 As DrawingDocument
		oDrawDoc3 = ThisApplication.Documents.Open(BList(x), True)
		oDrawDoc3.Activate
		oDrawDoc3 = ThisApplication.ActiveDocument
	
		Dim oDrgPrintMgr3 As DrawingPrintManager
		oDrgPrintMgr3 = oDrawDoc3.PrintManager
		With oDrgPrintMgr3
			.Printer = "\\lesg-dc-003\HP Color LaserJet 5550 PCL6 Black and White"
			.ColorMode = kPrintGrayScale
			.AllColorsAsBlack = True
			.ScaleMode = kPrintFullScale
			.PrintRange = kPrintAllSheets
			.Orientation = kLandscapeOrientation
			.RemoveLineWeights = False
		End With
		oDrgPrintMgr3.PaperSize = PaperSizeEnum.kPaperSize11x17
		oDrgPrintMgr3.SubmitPrint
		oDrawDoc3.Close (True)
	Next x
End If

'output to know the script is finished
MsgBox(numFiles & " printed.")

excelWorkbook.Save
excelWorkbook.Close
excelApp.Quit
excelApp = Nothing
